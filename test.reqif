# Specification: SW specification

## R1: SWRQT-ANGLE_CALCUL (Requirement)
- Author: Hallo
- Author: Hallo2
- selflink -> R2

## R2: SWRQT-FIELD_CALCUL (Requirement)
- Author: Hallo3
- Author: Hallo4

# Specification: SW Unit test plan

## R3: UTEST-ANGLE_CALCUL (Test Case)
- Author: Utest_1
- Author: utest_2
- selflink -> R4

## R4: UTEST-FIELD_CALCUL (Test Case)
- Author: Utest_3
- Author: Utest_4
